FME workspace BGT downloaden naar Excel.fmw

Parameters:
- DestDataset_XLSXW = P:\Projecten\CO2 Voetafdruk\Circulariteitsmonitor 2023\BGT Wegen\BGT_Wegen_IenW.xlsx   # Destination Microsoft Excel File
- GEMEENTENAAM_PAR = Hoorn   # Vul hier een gemeentenaam in
- SourceDataset_GEODATABASE_SDE = \\pds\cloud$\gis_enterprise\databeheer\db_connecties\Eigenaar\GPPUB\brondata_gppub.sde   # Connection File
- DestDataset_CSV2 = P:\Werkprocessen\CO2 Voetafdruk\Circulariteitsmonitor 2023\BGT Wegen   # Destination CSV (Comma Separated Value) Folder

Readers:
- GEODATABASE_SDE_1: GEODATABASE_SDE
- GEODATABASE_SDE_2: GEODATABASE_SDE from $(SourceDataset_GEODATABASE_SDE)

Writers:
- XLSXW_1: XLSXW to $(DestDataset_XLSXW)
- CSV2_1: CSV2 to $(DestDataset_CSV2)

AG_PROVINCIES_LAND_NL (reader GEODATABASE_SDE_2)
    attributes: objectid integer, provincienaam char(25), provinciecode char(10), abf_code smallint, st_area(shape) double, st_perimeter(shape) double
    -> AttributeFilter
AttributeFilter
    ATTR_NAME = provincienaam
    ATTR_VALUES = <Empty>,<Missing>,<Null>,<Unfiltered>,Drenthe,Flevoland,Friesland,Gelderland,Groningen,Limburg,Noord-Brabant,Noord-Holland,Overijssel,Utrecht,Zeeland,Zuid-Holland
    PRESERVE_FEATURE_ORDER_LOOKUP = PER_OUTPUT_PORT
    Zuid-Holland -> Deaggregator
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> DonutHoleExtractor
DonutHoleExtractor
    DEAGGREGATE_INPUT = Yes
    OUTERSHELL -> BGT-downloader [Polygon]
AG_GEMEENTEN_LAND_V (reader GEODATABASE_SDE_1) [off]
    attributes: objectid integer, code char(254), gemeentenaam char(254), burg_naam char(254), burg_nr char(254), prov_naam char(254), url_gemeente char(255), st_area(shape) double, st_perimeter(shape) double
    -> BGT-downloader [Polygon]
BGT-downloader
    domain = https://api.pdok.nl
    feature_types = wegdeel
    format = "gmllight"
    output_filename = Generate filename automatically
    output_folder = D:\Users\pnh08839\Downloads
    ZIP-Filepath -> BGT-processor [BGT-download]
BGT-processor
    bgt_download_zipfile_path = @Value(_response_file_path)
    feature_types = _PROCESS_FULL_DOWNLOAD
    process_options = current_objects expose_attributes
    spatial_filter = Initiator Intersects Result
    Processed -> Tester_2
Tester_2
    BOOL_OP = OR
    TEST_CLAUSE = TEST @Value(Bronhouder) = L0002
    TEST_MODE = TEST
    PASSED -> GeometryFilter
GeometryFilter
    FILTER_MODE = SIMPLE
    FILTER_MULTI = FILTER_TYPES]"Point Curve Area"]FME_CONTROLLER_QUERY_FILE]]FME_CONTROLLER_CHOICE]Simple
    Area -> AreaCalculator
AreaCalculator
    AREA_ATTR = _area
    AREA_TYPE = Plane Area
    MULT = 1
    -> StringReplacer
StringReplacer
    CASE = NO
    FIND_TEXT = .
    NO_MATCH = _FME_NO_OP_
    REGEXP = NO
    REPLACE_TEXT = ,
    SRC_ATTRS = _area
    -> Counter
Counter
    CNT_ATTR = _count
    DOMAIN = counter
    SCOPE = Global
    START = 0
    -> Tester
Tester
    BOOL_OP = OR
    TEST_CLAUSE = TEST @Value(_count) > 1000000
    TEST_MODE = TEST
    FAILED -> Sheet1 (writer XLSXW_1) [off]
    FAILED -> BGT_Wegen_Gelderland (writer CSV2_1)

Bookmark: Writers
Sheet1 (writer XLSXW_1)
    attributes: objectid number(20), provincienaam string(25), provinciecode string(10), BeginTijd string(200), EindTijd string(200), IdentificatieNamespace string(200), IdentificatieLokaalID string(200), TijdstipRegistratie string(200), Bronhouder string(200), InOnderzoek string(200), RelatieveHoogteligging string(200), BgtStatus string(200), PlusStatus string(200), BgtType string(200), PlusType string(200), BgtFysiekVoorkomen string(200), PlusFysiekVoorkomen string(200), OpTalud string(200), feature_type string(20), BgtFunctie string(200), EindRegistratie string(200), LV-publicatiedatum string(200), PlusFunctie string(200), _area number(20), _length number(20), _count number(20)
BGT_Wegen_Gelderland (writer CSV2_1)
    attributes: objectid int32, provincienaam varchar(25), provinciecode varchar(10), BeginTijd varchar(200), EindTijd varchar(200), IdentificatieNamespace varchar(200), IdentificatieLokaalID varchar(200), TijdstipRegistratie varchar(200), Bronhouder varchar(200), InOnderzoek varchar(200), RelatieveHoogteligging varchar(200), BgtStatus varchar(200), PlusStatus varchar(200), BgtType varchar(200), PlusType varchar(200), BgtFysiekVoorkomen varchar(200), PlusFysiekVoorkomen varchar(200), OpTalud varchar(200), feature_type string, BgtFunctie varchar(200), LV-publicatiedatum varchar(200), _area real64, _length real64

FME custom transformer BGT-downloader
BGT-downloader
Terralytics (Koen Verhoeven)
PDOK provides an API to download the BGT (Basisadministratie Grootschalige Topografie).
You can find the API over here: https://api.pdok.nl/lv/bgt/download/v1_0/ui/
With this transformer "BGT-downloader" you can download the data using your own geometry as input. 
Hint:
To minimize the amount of API-requests, try to aggregate your data before it enters the BGT-downloader.
Input
The transformer expects polygons as input data. For each polygon entering the transformer, a BGT-download will be returned for that area and some buffer around it. This buffer is created by the API, not by this transformer.
Data formats
The transformer provides three formats:
1. CityGML. This is the standard format with most options. When downloading deltas/mutations this is your only option. CityGML also contains expired/historic objects.
2. GMLLight. It is a lighter GML-format with less options. It contains expired/historic objects. 
3. StUF-Geo. This format contains the BGT data using the StUF-Geo format.
Parameter settings
Format: choose for one of the three data formats described above.
Feature types: choose the feature types you would like to download. By default alle feature types except 'Plaatsbepalingspunten' are selected.
Only mutations after date: For the CityGML format it is possible to download the deltas. This means only objects after a given date will be returned by the API. Use the setting 'mutations after date' to select the startdate of the mutations you need. Important: Deltas are only available for last month and until the day before yesterday. 
Output folder: Choose the directory where the download will be saved
Output Filename: By default the filename will be generated automatically. You can override this by typing your own value. Make sure the filename ends with .zip
Output ports
Zip-Filepath: Returns the location of the downloaded zip-file.
Rejected: Returns rejected features. Check logfile for the reason of rejection.
Process data
In one of the earlier versions the transformer also contained options to process the data. To improve the usability of the transformer, the processing moved to a new, separate transformer, the BGT-processor. 
Credits
The BGT-downloader is used a lot! Because of that I also received a lot of feedback for improvements:
Jan Droesen (Movares): Jan sent me his example of a custom transformer for processing the data. (v2) 
Michiel Faber (IDgis): Michiel gave feedback for improving the speed of the request status of the download. (v1.1)
Evelien Droge (Cobra groeninzicht): Evelien helped me with testing and provided some useful feedback. (v1)
Lars de Vries (Omkeere) for the idea to add the GML-axis order to avoid invalid geometry. (v2.3)
Pieter-Jan Demmers (Gemeente Heusden): Pieter-Jan gave me a lot of input, especially concerning the OpenbareRuimteLabels (v3)
Hans Pouw (Defensie Pijplijn Organisatie): Together with Hans we improved the transformer by using it as part of a bigger project. This resulted in many smaller improvements (v3)
Thanks for all the feedback!

Parameters:
- format = "citygml"   # Format
- feature_types = bak begroeidterreindeel bord buurt functioneelgebied gebouwinstallatie installatie kast kunstwerkdeel mast onbegroeidterreindeel ondersteunendwaterdeel ondersteunendwegdeel ongeclassificeerdobject openbareruimte openbareruimtelabel overbruggingsdeel overigbouwwerk overigescheiding paal pand put scheiding sensor spoor stadsdeel straatmeubilair tunneldeel vegetatieobject waterdeel waterinrichtingselement waterschap wegdeel weginrichtingselement wijk   # Feature types
- date_delta =   # "{}" Only mutations after date
- output_folder =   # Output Folder
- output_filename = Generate filename automatically   # "Generate filename automatically"%ManualFilename.zip Output Filename (.zip)
- domain = https://api.pdok.nl   # Domain

Note: probleem bij geen beschikbare delta nu opgelost met max 2 dagen van tevoren, maar dat moet beter kunnen
TestFilter
    DEFAULT_VALUE = Full download
    PASSED_TEST_GROUP_OUTPUT = FIRST
    TEST_LIST:
      "BOOL_OP,AND,COMPOSITE_TEST,""""""1"""""",TEST_CLAUSE,TEST @Value(_date_delta) > @DateTimeAdd(@DateTimeNow(),-P2D)",Delta not available yet,"BOOL_OP,AND,COMPOSITE_TEST,""""""1 AND 2"""""",TEST_CLAUSE,TEST _date_delta ATTRIBUTE_HAS_A_VALUE ""
      TEST $(format) = "citygml"",Download deltas
    Delta not available yet -> Logger_3
    Download deltas -> HTTPCaller_5
    Full download -> AttributeCreator_2
Logger_3
    LOG_FEATURE = LOG_RECORD
    MAXCOORDS = 20
    MAXFEATS = 20
    MESSAGE = Selected mutation date for the delta download is newer than last available delta download from the API
    SEVERITY = WARN
    LOGGED -> <Rejected> (output)
<Rejected> (output)

Bookmark: Check and prepare geometry
Polygon (input)
    -> GeometryFilter
GeometryFilter
    BREAK_AGG_BOOL = 0
    GEOM_PORTS = AREA
    BREAK_AGG = No
    GEOM_PORT_NAMES = Area
    AREA -> MeasureRemover
    <UNFILTERED> -> Logger_2
Note: Nog niet getest
MeasureRemover
    REMOVE_ALL = Yes
    -> 2DForcer
2DForcer
    2D -> Reprojector
Note: API expects 28992
Reprojector
    DEST = EPSG:28992
    INTERPOLATION_TYPE = ,NearestNeighbor
    RASTER_CELL_SIZE_LOOKUP = ,PreserveCells
    RASTER_TOLERANCE = 0.0
    SOURCE = Read from feature
    INTERPOLATION_TYPE_NAME = Nearest Neighbor
    RASTER_CELL_SIZE = Preserve Cells
    REPROJECTED -> GeometryExtractor
GeometryExtractor
    ATTR = _geofilter
    KIND = wkt
    OGCVERSION = 1.2
    OGC_WKT_PRECISION = FLOAT_64
    REMOVE_GEOMETRY = No
    KIND_LONG = OGC Well Known Text
    OGC_WKT_PRECISION_DISPLAY = 64-bit
    -> ParameterFetcher
    <REJECTED> -> <Rejected> (output)
Logger_2
    LOG_FEATURE = LOG_ONLY
    MAXCOORDS = 20
    MAXFEATS = 20
    MESSAGE = input should be a polygon / area
    SEVERITY = ERROR
    LOGGED -> <Rejected> (output)

Bookmark: Get params
ParameterFetcher
    ATTR_LIST = _feature_types $(feature_types) _date_delta $(date_delta)
    -> StringReplacer
StringReplacer
    CASE = NO
    FIND_TEXT = " "
    NO_MATCH = _FME_NO_OP_
    REGEXP = NO
    REPLACE_TEXT = ","
    SRC_ATTRS = _feature_types
    -> TestFilter

Bookmark: Get all deltaid's and select the correct deltaid which corresponds with the desired startdate
HTTPCaller_5
    CONNECTION_TIMEOUT_LENGTH = 60
    ERROR_ATTR = _error
    FOLLOW_REDIRECTS = Yes
    HTTP_METHOD = GET
    SAVE_FILE_LOOKUP = NO
    STATUS_CODE_ATTR = _http_status_code
    TARGET_ATTR = _response_body
    TARGET_ATTR_ENCODING = auto-detect
    TARGET_URL = https://api.pdok.nl/lv/bgt/download/v1_0/delta?count=1000
    TRANSFER_TIMEOUT_LENGTH = 90
    USE_COOKIES = No
    VERIFY_SSL_CERTIFICATES = Yes
    SAVE_FILE = Attribute
    -> JSONFragmenter
JSONFragmenter
    EXPLODE_FORMAT = JSON
    EXTRACT_ATTR = Yes
    JSON_ATTR = _response_body
    JSON_QUERY = json["deltas"][*]
    NEW_ATTRIBUTES = id timeWindow.from
    READ_FROM_FILE = NO
    RECURSIVE_LOOKUP = YES
    REJECT_EMPTY_LISTS = YES
    RECURSIVE = Yes
    FRAGMENTS -> DateTimeConverter
DateTimeConverter
    DATETIME_ATTR = timeWindow.from
    OUT_FORMAT = %Y%m%d%H%M%S
    PASSTHROUGH = NO
    REPAIR_INPUT = YES
    -> TestFilter_11
Note: hier nog op een of andere manier een check toevoegen of er uberhaupt één delta kan worden gevonden (zonder gebruik te maken van blocking transformers en attributecreators met subsequent features)
TestFilter_11
    DEFAULT_VALUE = <UNFILTERED>
    PASSED_TEST_GROUP_OUTPUT = FIRST
    TEST_LIST = "BOOL_OP,OR,COMPOSITE_TEST,""""""1"""""",TEST_CLAUSE,TEST @Value(timeWindow.from) > $(date_delta)",new delta(s) available
    new delta(s) available -> Sampler
Sampler
    MODE = ORIGINAL
    RATE = 1
    SAMPLE_TYPE_MULTIPLIER = -1
    SAMPLE_MODE = No
    SAMPLE_TYPE_LONG = First N Features
    SAMPLED -> AttributeCreator_6

Bookmark: Prepare and post request
Note: https://api.pdok.nl/lv/bgt/download/v1_0/ui/#/
AttributeCreator_6
    ATTR_TABLE:
      SET_TO _request_body = {
          "featuretypes": ["@Value(_feature_types)"
          ],
          "format": "citygml",
          "deltaId": "@Value(id)",
          "geofilter": "@Value(_geofilter)"
        }
      SET_TO _request_url = $(domain)/lv/bgt/download/v1_0/delta/custom
    -> HTTPCaller
Note: https://api.pdok.nl/lv/bgt/download/v1_0/ui/
AttributeCreator_2
    ATTR_TABLE:
      SET_TO _request_body = {
          "featuretypes": ["@Value(_feature_types)"
          ],
          "format": $(format),
          "geofilter": "@Value(_geofilter)"
        }
      SET_TO _request_url = $(domain)/lv/bgt/download/v1_0/full/custom
    -> HTTPCaller
HTTPCaller
    CONNECTION_TIMEOUT_LENGTH = 60
    CONTENT_TYPE_LOOKUP = application/json
    ERROR_ATTR = _error
    FOLLOW_REDIRECTS = Yes
    HTTP_METHOD = POST
    SAVE_FILE_LOOKUP = NO
    STATUS_CODE_ATTR = _http_status_code
    TARGET_ATTR = _response_body
    TARGET_ATTR_ENCODING = auto-detect
    TARGET_URL = @Value(_request_url)
    TRANSFER_TIMEOUT_LENGTH = 90
    UPLOAD_BODY = @Value(_request_body)
    UPLOAD_TYPE = Specify Upload Body
    USE_COOKIES = No
    VERIFY_SSL_CERTIFICATES = Yes
    SAVE_FILE = Attribute
    UPLOAD_CONTENT_TYPE = JSON (application/json)
    -> TestFilter_12
    <REJECTED> -> <Rejected> (output)

Bookmark: Post request for data preparation
TestFilter_12
    DEFAULT_VALUE = Failure
    PASSED_TEST_GROUP_OUTPUT = FIRST
    TEST_LIST = "BOOL_OP,OR,COMPOSITE_TEST,""""""1"""""",TEST_CLAUSE,TEST @Value(_http_status_code) = 202",Success
    Success -> JSONExtractor
    Failure -> <Rejected> (output)
JSONExtractor
    EXTRACT_QUERY_TABLE = href_status json["_links"]["status"]["href"] downloadRequestId json["downloadRequestId"]
    JSON_DOCUMENT = @Value(_response_body)
    READ_FROM_FILE = NO
    EVALUATED -> Decelerator
    <REJECTED> -> <Rejected> (output)
Note: wait a few seconds to let the API prepare the data
Decelerator
    DECEL_LOOKUP = PERFEATDELAY
    DELAY = 5
    DECEL_TYPE = Per Feature Delay
    -> HTTPCaller_2

Bookmark: Get request status
Requested_data (input)
    -> HTTPCaller_2
HTTPCaller_2
    CONNECTION_TIMEOUT_LENGTH = 60
    ERROR_ATTR = _error
    FOLLOW_REDIRECTS = Yes
    HTTP_METHOD = GET
    SAVE_FILE_LOOKUP = NO
    STATUS_CODE_ATTR = _http_status_code
    TARGET_ATTR = _response_body
    TARGET_ATTR_ENCODING = auto-detect
    TARGET_URL = $(domain)@Value(href_status)
    TRANSFER_TIMEOUT_LENGTH = 90
    USE_COOKIES = No
    VERIFY_SSL_CERTIFICATES = Yes
    SAVE_FILE = Attribute
    -> AttributeFilter
    <REJECTED> -> <Rejected> (output)
Note: 200: File is NOT yet ready for download / 201: File is ready for download
AttributeFilter
    ATTR_NAME = _http_status_code
    ATTR_VALUES = <Empty>,<Missing>,<Null>,<Unfiltered>,201,200
    PRESERVE_FEATURE_ORDER_LOOKUP = PER_OUTPUT_PORT
    <UNFILTERED> -> <Rejected> (output)
    201 -> JSONExtractor_2
    200 -> Counter
Counter
    CNT_ATTR = _count
    DOMAIN = @Value(downloadRequestId)
    SCOPE = Local
    START = 1
    SCOPEVAR = Local
    -> TestFilter_2
Note: max 1000 loops
TestFilter_2
    DEFAULT_VALUE = Abort
    PASSED_TEST_GROUP_OUTPUT = FIRST
    TEST_LIST = "BOOL_OP,OR,COMPOSITE_TEST,""""""1"""""",TEST_CLAUSE,TEST @Value(_count) < 1000",Continue
    Continue -> Decelerator_2
    Abort -> Logger
Note: wait for one second
Decelerator_2
    DECEL_LOOKUP = PERFEATDELAY
    DELAY = 1
    DECEL_TYPE = Per Feature Delay
    -> Requested_data (output)
Requested_data (output)
Logger
    LOG_FEATURE = LOG_ONLY
    MAXCOORDS = 20
    MAXFEATS = 20
    MESSAGE = data preparation took more than 1000 seconds
    SEVERITY = ERROR
    LOGGED -> <Rejected> (output)
JSONExtractor_2
    EXTRACT_QUERY_TABLE = href_download json["_links"]["download"]["href"] progress json["progress"] status json["status"]
    JSON_DOCUMENT = @Value(_response_body)
    READ_FROM_FILE = NO
    EVALUATED -> TestFilter_10
    <REJECTED> -> <Rejected> (output)

Bookmark: Get download result
Download_data_errors (input)
    -> TestFilter_10
TestFilter_10
    DEFAULT_VALUE = Generate filenames automatically
    PASSED_TEST_GROUP_OUTPUT = FIRST
    TEST_LIST = "BOOL_OP,OR,COMPOSITE_TEST,""""""1"""""",TEST_CLAUSE,CASE_INSENSITIVE_TEST $(output_filename) ENDS_WITH .zip",Manual filename
    Manual filename -> HTTPCaller_6
    Generate filenames automatically -> HTTPCaller_3
HTTPCaller_6
    CONNECTION_TIMEOUT_LENGTH = 60
    ERROR_ATTR = _error
    FILE_PATH_ATTR = _response_file_path
    FOLLOW_REDIRECTS = Yes
    HTTP_METHOD = GET
    OUTPUT_FILENAME = $(output_folder)\$(output_filename)
    SAVE_FILE_LOOKUP = YES
    SAVE_MULTI = No
    STATUS_CODE_ATTR = _http_status_code
    TARGET_URL = $(domain)@Value(href_download)
    TRANSFER_TIMEOUT_LENGTH = 90
    USE_COOKIES = No
    VERIFY_SSL_CERTIFICATES = Yes
    SAVE_FILE = File
    -> ZIP-Filepath (output)
    <REJECTED> -> TestFilter_5
HTTPCaller_3
    CONNECTION_TIMEOUT_LENGTH = 60
    ERROR_ATTR = _error
    FILE_PATH_ATTR = _response_file_path
    FILE_TYPE_LOOKUP = AUTO_DETECT
    FOLLOW_REDIRECTS = Yes
    HTTP_METHOD = GET
    OUTPUT_DIRNAME = $(output_folder)
    SAVE_FILE_LOOKUP = YES
    SAVE_MULTI = Yes
    STATUS_CODE_ATTR = _http_status_code
    TARGET_URL = $(domain)@Value(href_download)
    TRANSFER_TIMEOUT_LENGTH = 90
    USE_COOKIES = No
    VERIFY_SSL_CERTIFICATES = Yes
    FILE_TYPE = <Auto Detect from HTTP Headers>
    SAVE_FILE = File
    -> ZIP-Filepath (output)
    <REJECTED> -> TestFilter_5
ZIP-Filepath (output)

Bookmark: Data download failure loop
TestFilter_5
    DEFAULT_VALUE = <UNFILTERED>
    PASSED_TEST_GROUP_OUTPUT = FIRST
    TEST_LIST = "BOOL_OP,OR,COMPOSITE_TEST,""""""1"""""",TEST_CLAUSE,TEST @Value(_error) = Failure when receiving data from the peer",Failure when receiving data from the peer
    Failure when receiving data from the peer -> Counter_2
    <UNFILTERED> -> Junction_2
Counter_2
    CNT_ATTR = _count2
    DOMAIN = @Value(downloadRequestId)
    SCOPE = Local
    START = 1
    SCOPEVAR = Local
    -> TestFilter_7
Note: max 5 loops
TestFilter_7
    DEFAULT_VALUE = Abort
    PASSED_TEST_GROUP_OUTPUT = FIRST
    TEST_LIST = "BOOL_OP,OR,COMPOSITE_TEST,""""""1"""""",TEST_CLAUSE,TEST @Value(_count2) <= 5",Continue
    Continue -> Decelerator_3
    Abort -> Logger_7
Decelerator_3
    DECEL_LOOKUP = PERFEATDELAY
    DELAY = 2
    DECEL_TYPE = Per Feature Delay
    -> Download_data_errors (output)
Download_data_errors (output)
Logger_7
    LOG_FEATURE = LOG_ONLY
    MAXCOORDS = 20
    MAXFEATS = 20
    MESSAGE = Data download not available: @Value(_error)
    SEVERITY = ERROR
    LOGGED -> Junction_2
Junction_2
    -> <Rejected> (output)

FME custom transformer BGT-processor
BGT-processor
Terralytics (Koen Verhoeven)
This transformer processes a previously downloaded BGT ZIP-file. The BGT can be downloaded using the custom transformer BGT-downloader or directly using the PDOK BGT API.
Input
The transformer expects a path to a ZIP-file containing a BGT-download. The ZIP-file may contain CityGML-files, GMLLight files or StUF-Geo files. The type of file is recognized automatically.
Parameter settings
BGT download ZIP-file path: the path to a ZIP-file containing a BGT-download. By default the response file path of the BGT-downloader is used.
Feature types:  choose the feature types you would like to process. By default all feature types within the download are processed.
Process options:
Expose and rename common attributes: When set, the transformer will rename and expose the most common attributes. Not all attributes are exposed and renamed. So check the data with the inspector if you miss some attributes for your own process. 
Process kruinlijnen: Kruinlijnen are the highest point of an area on a slope (Talud). By default, kruinlijnen are a geometry collection with the area on the slope. When this option is set, the geometry collections are split into a line (Kruinlijn) and polygon.
Only current objects: If selected, the transformer only returns existing, active objects. So basically everything you would like to see on a map as the current situation. When the StUF-GEO format is used it only returns the 'Wordt' objects (and no 'Was') objects.
Spatial filter: The PDOK API by default returns a bigger area than requested. So in most cases the data needs to be filtered. The spatial filter by default returns all objects which intersect with the intiator/input. 
Output ports
SchemaFeatures: Returns the schema for all formats
RawData: Returns the downloaded objects without exposing and renaming attributes. The RawData is always returned.
Processed: Returns the downloaded objects after exposing and renaming the most common BGT-attributes. Not all attributes are exposed and renamed. So check the data with the inspector if you miss some attributes for your own process. 
Rejected: Returns rejected features. Check logfile for the reason of rejection.

Parameters:
- bgt_download_zipfile_path = @Value(_response_file_path)   # BGT download ZIP-file path
- feature_types = _PROCESS_FULL_DOWNLOAD   # Feature types
- process_options = process_kruinlijnen current_objects expose_attributes
- spatial_filter = Initiator Intersects Result

BGT-download (input)
    -> FeatureReader_6 [INITIATOR]
AttributeRemover_3
    REMOVE_ATTRS = path_extension,path_filename,_InlezenWas,path_rootname,_reader_error,_feature_types
    -> SchemaFeatures (output)
SchemaFeatures (output)
RawData (output)
Processed (output)
<Rejected> (output)

Bookmark: Read files in zip-file
FeatureReader_6
    ATTRS_TO_EXPOSE = path_filename path_extension path_rootname
    ATTR_ACCUM_MODE = Merge Initiator and Result
    ATTR_CONFLICT_RES = Use Result
    COMBINE_GEOM = Use Initiator
    DATASET = @Value(_response_file_path)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    <OTHER> -> TestFilter
TestFilter
    DEFAULT_VALUE = No correct BGT format
    PASSED_TEST_GROUP_OUTPUT = FIRST
    TEST_LIST:
      "BOOL_OP,OR,COMPOSITE_TEST,""""""1"""""",TEST_CLAUSE,TEST @Value(path_filename) = bgt_all.xml",StUF-Geo,"BOOL_OP,OR,COMPOSITE_TEST,""""""1 OR 2"""""",TEST_CLAUSE,TEST @Value(path_extension) = gml
      TEST @Value(path_extension) = xml",CityGML and GMLLight
    StUF-Geo -> TestFilter_2
    CityGML and GMLLight -> AttributeCreator_2
    No correct BGT format -> <Rejected> (output)

Bookmark: StUF-GEO
TestFilter_2
    DEFAULT_VALUE = All objects
    PASSED_TEST_GROUP_OUTPUT = FIRST
    TEST_LIST = "BOOL_OP,OR,COMPOSITE_TEST,""""""1"""""",TEST_CLAUSE,CASE_INSENSITIVE_TEST $(process_options) CONTAINS current_objects",Current objects only
    Current objects only -> AttributeCreator_3
    All objects -> AttributeCreator
AttributeCreator_3
    ATTR_TABLE = SET_TO _InlezenWas = Slechts Wordt inlezen
    -> FeatureReader_5 [INITIATOR]
AttributeCreator
    ATTR_TABLE = SET_TO _InlezenWas = Was en Wordt inlezen
    -> FeatureReader_5 [INITIATOR]
Note: read entire StUF Geo
FeatureReader_5
    ATTRS_TO_EXPOSE = fme_feature_type
    ATTR_ACCUM_MODE = Merge Initiator and Result
    ATTR_CONFLICT_RES = Use Result
    COMBINE_GEOM = Use Result
    DATASET = @Value(_response_file_path)
    FORMAT = STUF-GEO
    INTERACT = <No Spatial Filter>
    OUTPUT_FEATURES_DISPLAY = Schema and Data Features
    STUF-GEO_InlezenWas = @Value(_InlezenWas)
    <SCHEMA> -> AttributeRemover_3
    <OTHER> -> AttributeCreator_4
    INITIATOR -> Junction_8
    <REJECTED> -> <Rejected> (output)
Junction_8
    -> SpatialFilter_5 [Filter]
    -> SpatialFilter_3 [Filter]
AttributeCreator_4
    ATTR_TABLE:
      SET_TO _feature_types = @ReplaceString( $(feature_types) , , _)
      SET_TO feature_type = @LowerCase(@Value(fme_feature_type))
      SET_TO feature_type_test = _@Value(feature_type)
    -> TestFilter_11
Note: Build-in workarounds stuf-geo reader: / - fix typo: gebouwinrichtingslement = gebouwinstallatie / - when processing 'pand', nummeraanduidingreeks is also processed / - kruinlijnen are processed when set by parameter
TestFilter_11
    DEFAULT_VALUE = <UNFILTERED>
    PASSED_TEST_GROUP_OUTPUT = FIRST
    TEST_LIST:
      "BOOL_OP,COMPOSITE,COMPOSITE_TEST,""""""1 OR 2 OR ( 3 AND 4 )
       OR ( 5 AND 6 )"""""",TEST_CLAUSE,CASE_INSENSITIVE_TEST @Value(_feature_types) CONTAINS @Value(feature_type_test)
      CASE_INSENSITIVE_TEST @Value(_feature_types) CONTAINS PROCESS_FULL_DOWNLOAD
      CASE_INSENSITIVE_TEST @Value(_feature_types) CONTAINS _gebouwinstallatie
      CASE_INSENSITIVE_TEST @Value(feature_type_test) = _gebouwinrichtingselement
      CASE_INSENSITIVE_TEST @Value(_feature_types) CONTAINS _pand
      CASE_INSENSITIVE_TEST @Value(feature_type_test) = _nummeraanduidingreeks",Process,"BOOL_OP,AND,COMPOSITE_TEST,""""""1 AND 2"""""",TEST_CLAUSE,CASE_INSENSITIVE_TEST $(process_options) CONTAINS process_kruinlijnen
      CASE_INSENSITIVE_TEST @Value(feature_type) = kruinlijn",Process kruinlijnen
    Process -> SpatialFilter_5 [Candidate]
    Process kruinlijnen -> SpatialFilter_5 [Candidate]
Note: spatialFilter after reading is faster in this case
SpatialFilter_5
    AGGREGATE_HANDLING = No
    BASE_TYPE = Multiple Filters
    CURVE_BOUNDARY_RULE_PARAM = Default Rule
    PASS_CRITERIA = Pass Against One Filter
    PREDICATES = FME_CONDITIONAL:DEFAULT_VALUE'CONTAINS'BOOL_OP;OR;COMPOSITE_TEST;1;TEST $(spatial_filter) = Bounding Box Intersect'CONTAINS'BOOL_OP;OR;COMPOSITE_TEST;1;TEST $(spatial_filter) = Initiator Intersects Result'INTERSECTS'BOOL_OP;OR;COMPOSITE_TEST;1;TEST $(spatial_filter) = Initiator Contains Result'CONTAINS'BOOL_OP;OR;COMPOSITE_TEST;1;TEST $(spatial_filter) = Initiator Crosses Result'CROSSES'BOOL_OP;OR;COMPOSITE_TEST;1;TEST $(spatial_filter) = Initiator is Disjoint from Result'DISJOINT'BOOL_OP;OR;COMPOSITE_TEST;1;TEST $(spatial_filter) = Initiator Equals Result'EQUALS'BOOL_OP;OR;COMPOSITE_TEST;1;TEST $(spatial_filter) = Initiator Overlaps Result'OVERLAPS'BOOL_OP;OR;COMPOSITE_TEST;1;TEST $(spatial_filter) = Initiator Touches Result'TOUCHES'BOOL_OP;OR;COMPOSITE_TEST;1;TEST $(spatial_filter) = Initiator is Within Result'WITHIN'BOOL_OP;OR;COMPOSITE_TEST;1;TEST $(spatial_filter) = <No Spatial Filter>'CONTAINS INTERSECTS DISJOINT'FME_NUM_CONDITIONS11___
    USE_BOUNDING_BOX = No
    PASSED -> AttributeRemover_2
    <REJECTED> -> SpatialFilter_3 [Candidate]
Note: Support for aggregates (but less support for spatial filter possibilities/predicates)
SpatialFilter_3
    AGGREGATE_HANDLING = Yes
    BASE_TYPE = Multiple Filters
    CURVE_BOUNDARY_RULE_PARAM = Default Rule
    PASS_CRITERIA = Pass Against One Filter
    PREDICATES = FME_CONDITIONAL:DEFAULT_VALUE'CONTAINS'BOOL_OP;OR;COMPOSITE_TEST;1;TEST $(spatial_filter) = Bounding Box Intersect'CONTAINS'BOOL_OP;OR;COMPOSITE_TEST;1;TEST $(spatial_filter) = Initiator Intersects Result'INTERSECTS'BOOL_OP;OR;COMPOSITE_TEST;1;TEST $(spatial_filter) = Initiator Contains Result'CONTAINS'BOOL_OP;OR;COMPOSITE_TEST;1;TEST $(spatial_filter) = Initiator Crosses Result'CROSSES'BOOL_OP;OR;COMPOSITE_TEST;1;TEST $(spatial_filter) = Initiator is Disjoint from Result'DISJOINT'BOOL_OP;OR;COMPOSITE_TEST;1;TEST $(spatial_filter) = Initiator Equals Result'EQUALS'BOOL_OP;OR;COMPOSITE_TEST;1;TEST $(spatial_filter) = Initiator Overlaps Result'OVERLAPS'BOOL_OP;OR;COMPOSITE_TEST;1;TEST $(spatial_filter) = Initiator Touches Result'TOUCHES'BOOL_OP;OR;COMPOSITE_TEST;1;TEST $(spatial_filter) = Initiator is Within Result'WITHIN'BOOL_OP;OR;COMPOSITE_TEST;1;TEST $(spatial_filter) = <No Spatial Filter>'CONTAINS INTERSECTS DISJOINT'FME_NUM_CONDITIONS11___
    USE_BOUNDING_BOX = No
    PASSED -> AttributeRemover_2
    <REJECTED> -> <Rejected> (output)

Bookmark: Attribute cleanup and exposing
AttributeRemover_2
    REMOVE_ATTRS = path_extension,feature_type,path_filename,_matched_records,_InlezenWas,fme_rejection_code,_response_file_path,feature_type_test,path_rootname,_feature_types
    -> TestFilter_4
Note: RawData is always exported
TestFilter_4
    DEFAULT_VALUE = Only RawData
    PASSED_TEST_GROUP_OUTPUT = FIRST
    TEST_LIST = "BOOL_OP,OR,COMPOSITE_TEST,""""""1"""""",TEST_CLAUSE,CASE_INSENSITIVE_TEST $(process_options) CONTAINS expose_attributes",Expose attributes
    Expose attributes -> AttributeExposer
    Expose attributes -> Junction_4
    Only RawData -> Junction_4
Junction_4
    -> RawData (output)
AttributeExposer
    ATTR_LIST = BeginTijd,EindTijd,IdentificatieNamespace,IdentificatieLokaalID,TijdstipRegistratie,Bronhouder,InOnderzoek,RelatieveHoogteligging,BgtStatus,PlusStatus,BgtType,PlusType,BgtFysiekVoorkomen,PlusFysiekVoorkomen,OpTalud
    -> Processed (output)

Bookmark: Select feature to process
AttributeCreator_2
    ATTR_TABLE = SET_TO _feature_types = @ReplaceString( $(feature_types) , , bgt_)
    -> TestFilter_3
TestFilter_3
    DEFAULT_VALUE = <UNFILTERED>
    PASSED_TEST_GROUP_OUTPUT = FIRST
    TEST_LIST:
      "BOOL_OP,COMPOSITE,COMPOSITE_TEST,""""""1 AND ( 2 OR 3 )"""""",TEST_CLAUSE,CASE_INSENSITIVE_TEST @Value(path_rootname) = bgt_openbareruimtelabel
      CASE_INSENSITIVE_TEST @Value(_feature_types) CONTAINS  @Value(path_rootname)
      CASE_INSENSITIVE_TEST @Value(_feature_types) CONTAINS PROCESS_FULL_DOWNLOAD",Process ORL,"BOOL_OP,OR,COMPOSITE_TEST,""""""1 OR 2"""""",TEST_CLAUSE,CASE_INSENSITIVE_TEST @Value(_feature_types) CONTAINS  @Value(path_rootname)
      CASE_INSENSITIVE_TEST @Value(_feature_types) CONTAINS PROCESS_FULL_DOWNLOAD",Process
    Process ORL -> FeatureReader_8 [INITIATOR]
    Process -> FeatureReader_9 [INITIATOR]
    Process -> FeatureReader_7 [INITIATOR]

Bookmark: CityGML and GMLLight
Note: Process ORLs. ORLs are not valid CityGML and therefore require separate processing. / ToDo: equalize ORL attribute names with citygml
FeatureReader_8
    ATTR_ACCUM_MODE = Only Use Result
    COMBINE_GEOM = Use Result
    COORDSYS = EPSG:28992
    DATASET = @Value(_response_file_path)\@Value(path_filename)
    FEATURETYPES = OpenbareRuimteLabel
    FORMAT = GML
    GML_CACHE_XSD = yes
    GML_CONTINUE_ON_GEOM_ERROR = yes
    GML_ENFORCE_PATH_CONTINUITY_BY = SNAPPING_END_POINTS
    GML_EXPLORE_XSD_VALUES = NO
    GML_FEATURE_TYPES_SCHEMA_MODE = XML_SCHEMA
    GML_FLATTEN_XML_FRAGMENTS = NO
    GML_IGNORE_APPLICATON_SCHEMA = yes
    GML_MAP_ALL_SUBSTITUTABLE_PROPERTIES = YES
    GML_MULTI_VALUE_SIMPLE_PROPERTIES_AS_CSV = no
    GML_REPROJECT_DISPARATE_CRS_IN_MULTIPLE_GEOMETRIES = yes
    GML_USE_OLD_READER = NO
    GML_USE_SEARCH_ENVELOPE = NO
    GML_VALIDATE_DATASET = no
    INTERACT = $(spatial_filter)
    OUTPUT_FEATURES_DISPLAY = Schema and Data Features
    <SCHEMA> -> AttributeRemover_3
    <OTHER> -> TestFilter_5
    <REJECTED> -> <Rejected> (output)
Note: read CityGML
FeatureReader_9 [off]
    ATTRS_TO_EXPOSE = fme_feature_type
    ATTR_ACCUM_MODE = Merge Initiator and Result
    ATTR_CONFLICT_RES = Use Result
    CITYGML_ADD_NAMESPACE_PREFIX_TO_FEATURE_TYPES = No
    CITYGML_GENERIC_ATTRS_AS_FEATURES = No
    CITYGML_GENERIC_ATTRS_AS_SCHEMA_ATTRS = Yes
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_SRS_AXIS_ORDER = 1,2
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    COORDSYS = EPSG:28992
    DATASET = @Value(_response_file_path)\@Value(path_filename)
    FORMAT = CITYGML
    INTERACT = $(spatial_filter)
    OUTPUT_FEATURES_DISPLAY = Schema and Data Features
    <SCHEMA> -> AttributeRemover_3
    <OTHER> -> AttributeCopier
    <REJECTED> -> FeatureReader_7 [INITIATOR]
Note: read GMLLight
FeatureReader_7
    ATTRS_TO_EXPOSE = fme_feature_type
    ATTR_ACCUM_MODE = Merge Initiator and Result
    ATTR_CONFLICT_RES = Use Result
    COMBINE_GEOM = Use Result
    COORDSYS = EPSG:28992
    DATASET = @Value(_response_file_path)\@Value(path_filename)
    FORMAT = GML
    GML_CACHE_XSD = yes
    GML_CONTINUE_ON_GEOM_ERROR = yes
    GML_ENFORCE_PATH_CONTINUITY_BY = SNAPPING_END_POINTS
    GML_EXPLORE_XSD_VALUES = NO
    GML_FEATURE_TYPES_SCHEMA_MODE = DATASET_ONLY
    GML_FLATTEN_XML_FRAGMENTS = NO
    GML_IGNORE_APPLICATON_SCHEMA = yes
    GML_MAP_ALL_SUBSTITUTABLE_PROPERTIES = YES
    GML_MULTI_VALUE_SIMPLE_PROPERTIES_AS_CSV = no
    GML_REPROJECT_DISPARATE_CRS_IN_MULTIPLE_GEOMETRIES = yes
    GML_SRS_AXIS_ORDER = 1,2
    GML_USE_OLD_READER = NO
    GML_USE_SEARCH_ENVELOPE = NO
    GML_VALIDATE_DATASET = no
    INTERACT = $(spatial_filter)
    OUTPUT_FEATURES_DISPLAY = Schema and Data Features
    <SCHEMA> -> AttributeRemover_3
    <OTHER> -> AttributeCopier
    <REJECTED> -> <Rejected> (output)

Bookmark: Rename feature types
AttributeCopier
    ATTR_TABLE = COPY path_rootname > feature_type
    -> StringReplacer
StringReplacer
    CASE = NO
    FIND_TEXT = bgt_
    NO_MATCH = _FME_NO_OP_
    REGEXP = NO
    SRC_ATTRS = feature_type
    -> TestFilter_10

Bookmark: Kruinlijnen
TestFilter_10
    DEFAULT_VALUE = <UNFILTERED>
    PASSED_TEST_GROUP_OUTPUT = FIRST
    TEST_LIST = "BOOL_OP,OR,COMPOSITE_TEST,""""""1"""""",TEST_CLAUSE,CASE_INSENSITIVE_TEST $(process_options) CONTAINS process_kruinlijnen",Process kruinlijnen
    Process kruinlijnen -> GeometryFilter
    <UNFILTERED> -> Junction_2
Note: Vrebeterpunt: Ook hoogspanningsmast met geometrie-collectie worden nu verwerkt
GeometryFilter
    BREAK_AGG_BOOL = 0
    GEOM_PORTS = COLLECTION
    BREAK_AGG = No
    GEOM_PORT_NAMES = Collection
    COLLECTION -> Deaggregator_2
    <UNFILTERED> -> Junction_2
Deaggregator_2
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> GeometryFilter_4
GeometryFilter_4
    BREAK_AGG_BOOL = 0
    GEOM_PORTS = LINE ARC
    BREAK_AGG = No
    GEOM_PORT_NAMES = Line Arc
    LINE -> AttributeRenamer_4
    ARC -> AttributeRenamer_4
    <UNFILTERED> -> Junction_5
AttributeRenamer_4
    ATTR_TABLE = RENAME_SET_DEFAULT _geometry_name > feature_type
    -> Junction_5
Junction_2
    -> Junction_5
Junction_5
    -> TestFilter_5

Bookmark: Check current objects
TestFilter_5
    DEFAULT_VALUE = All objects
    PASSED_TEST_GROUP_OUTPUT = FIRST
    TEST_LIST = "BOOL_OP,OR,COMPOSITE_TEST,""""""1"""""",TEST_CLAUSE,CASE_INSENSITIVE_TEST $(process_options) CONTAINS current_objects",Current objects only
    Current objects only -> TestFilter_7
    All objects -> Junction
Note: https://geoforum.nl/t/eindregistratie-of-terminationdate-bgt/3610/2
TestFilter_7
    DEFAULT_VALUE = Terminated
    PASSED_TEST_GROUP_OUTPUT = FIRST
    TEST_LIST:
      "BOOL_OP,AND,COMPOSITE_TEST,""""""1 AND 2"""""",TEST_CLAUSE,TEST imgeo_eind_registratie{0} ATTRIBUTE_IS_MISSING ""
      TEST eindRegistratie ATTRIBUTE_IS_MISSING """,Current
    Current -> Junction
Junction
    -> AttributeRemover

Bookmark: Attribute cleanup and exposing
AttributeRemover
    LIST_ATTRS = _hierarchy_child_id_list{}
    REMOVE_ATTRS = path_extension,path_filename,_geometry_name,_hierarchy_parent_id,_part_number,_response_file_path,path_rootname,_hierarchy_id,_reader_error,_feature_types
    -> TestFilter_6
Note: RawData is always exported
TestFilter_6
    DEFAULT_VALUE = Only RawData
    PASSED_TEST_GROUP_OUTPUT = FIRST
    TEST_LIST = "BOOL_OP,OR,COMPOSITE_TEST,""""""1"""""",TEST_CLAUSE,CASE_INSENSITIVE_TEST $(process_options) CONTAINS expose_attributes",Expose attributes
    Expose attributes -> Junction_3
    Expose attributes -> BulkAttributeRemover_2
    Only RawData -> Junction_3
Junction_3
    -> RawData (output)
BulkAttributeRemover_2
    ATTR_EXP = codeSpace
    -> SchemaMapper_2
Note: Mapping of most important attributes
SchemaMapper_2
    DATASET = https://terralytics.nl/schemamapper
    FORMAT = XLSXR
    IDXDESTATTR = fme_feature_type
    IDXDESTCOL = ""
    IDXSOURCEATTR = fme_feature_type
    IDXSOURCECOL = ""
    MAP_ATTRS = origineel nieuw $(FME_ASC_16)
    ROW_ID_ATTR = _schemamapper_row_ids
    TABLE = Blad1
    XLSXR_ALLOW_DOLLAR_SIGNS = YES
    XLSXR_CASE_SENSITIVE_FEATURE_TYPES = YES
    XLSXR_CONFIGURATION_DATASET = https://terralytics.nl/schemamapper
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_SCAN_SCHEMA_IF_DYNAMIC = No
    XLSXR_SCHEMA = Blad1,0,origineel,char,56,,,1,nieuw,char,22,,,1,,,,NO,NO,1,https://terralytics.nl/schemamapper,"0,0,1,71",,NO,NO
    XLSXR_STRIP_SHEETNAME_SPACES = YES
    XLSXR_TABLELIST = Blad1
    XLSXR_USE_SCHEMA_OTHER_FILES = No
    MAPPED -> AttributeExposer_6
AttributeExposer_6
    ATTR_LIST = BeginTijd,BgtFunctie,BgtFysiekVoorkomen,BgtStatus,BgtType,Bronhouder,Class,DatumInwinning,EindRegistratie,EindTijd,Hoek,IdentificatieLokaalID,IdentificatieNamespace,InOnderzoek,InwinnendeInstantie,Inwinningsmethode,LV-publicatiedatum,Naam,Nauwkeurigheid,OpTalud,PlusFunctie,PlusFysiekVoorkomen,PlusStatus,PlusType,RelatieveHoogteligging,TijdstipRegistratie
    -> AttributeRemover_4
AttributeRemover_4
    REMOVE_ATTRS = _schemamapper_row_ids
    -> Processed (output)
